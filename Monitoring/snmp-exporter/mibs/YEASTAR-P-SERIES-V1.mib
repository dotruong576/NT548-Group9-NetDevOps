--
-- YEASTAR-P-SERIES-V1.my
-- MIB generated by MG-SOFT Visual MIB Builder Version 6.0  Build 88
-- Sunday, April 23, 2023 at 14:28:20
--

	YEASTAR-P-SERIES-V1 DEFINITIONS ::= BEGIN
 
		IMPORTS
			OBJECT-TYPE			
				FROM RFC-1212			
			enterprises			
				FROM RFC1155-SMI;
	
	
--
-- Node definitions
--
	
--  Node definitions
-- 
-- 1.3.6.1.4.1.22736
		-- 1.3.6.1.4.1.22736
		ippbxMib OBJECT IDENTIFIER ::= { enterprises 22736 }

		
--  1.3.6.1.4.1.22736.3
		-- 1.3.6.1.4.1.22736.3
		ippbxPModules OBJECT IDENTIFIER ::= { ippbxMib 3 }

		
--  1.3.6.1.4.1.22736.3.1
		-- 1.3.6.1.4.1.22736.3.1
		pSysinfo OBJECT IDENTIFIER ::= { ippbxPModules 1 }

		
--  1.3.6.1.4.1.22736.3.1.1
		-- 1.3.6.1.4.1.22736.3.1.1
		pProductModel OBJECT-TYPE
			SYNTAX OCTET STRING
			ACCESS read-only
			STATUS mandatory
			DESCRIPTION
				"Description."
			::= { pSysinfo 1 }

		
--  1.3.6.1.4.1.22736.3.1.2
		-- 1.3.6.1.4.1.22736.3.1.2
		pHardwareVersion OBJECT-TYPE
			SYNTAX OCTET STRING
			ACCESS read-only
			STATUS mandatory
			DESCRIPTION
				"Description."
			::= { pSysinfo 2 }

		
--  1.3.6.1.4.1.22736.3.1.3
		-- 1.3.6.1.4.1.22736.3.1.3
		pFirmwareVersion OBJECT-TYPE
			SYNTAX OCTET STRING
			ACCESS read-only
			STATUS mandatory
			DESCRIPTION
				"Description."
			::= { pSysinfo 3 }

		
--  1.3.6.1.4.1.22736.3.1.4
		-- 1.3.6.1.4.1.22736.3.1.4
		pSerialNumber OBJECT-TYPE
			SYNTAX OCTET STRING
			ACCESS read-only
			STATUS mandatory
			DESCRIPTION
				"Description."
			::= { pSysinfo 4 }

		
--  1.3.6.1.4.1.22736.3.1.5
		-- 1.3.6.1.4.1.22736.3.1.5
		pUptime OBJECT-TYPE
			SYNTAX OCTET STRING
			ACCESS read-only
			STATUS mandatory
			DESCRIPTION
				"Description."
			::= { pSysinfo 5 }

		
--  1.3.6.1.4.1.22736.3.1.6
		-- 1.3.6.1.4.1.22736.3.1.6
		pLocalStorageUsage OBJECT-TYPE
			SYNTAX OCTET STRING
			ACCESS read-only
			STATUS mandatory
			DESCRIPTION
				"Description."
			::= { pSysinfo 6 }

		
--  1.3.6.1.4.1.22736.3.1.7
		-- 1.3.6.1.4.1.22736.3.1.7
		pMemoryUsage OBJECT-TYPE
			SYNTAX OCTET STRING
			ACCESS read-only
			STATUS mandatory
			DESCRIPTION
				"Description."
			::= { pSysinfo 7 }


		-- 1.3.6.1.4.1.22736.3.1.8
		pCPUUtilization OBJECT-TYPE
			SYNTAX OCTET STRING
			ACCESS read-only
			STATUS mandatory
			::= { pSysinfo 8 }

		
		-- 1.3.6.1.4.1.22736.3.1.9
		pConcurrentCall OBJECT-TYPE
			SYNTAX INTEGER
			ACCESS read-only
			STATUS mandatory
			::= { pSysinfo 9 }

		
		-- 1.3.6.1.4.1.22736.3.1.10
		pAvgCpuLoad OBJECT-TYPE
			SYNTAX OCTET STRING
			ACCESS read-only
			STATUS mandatory
			::= { pSysinfo 10 }

		
		-- 1.3.6.1.4.1.22736.3.1.11
		pAsteriskStatus OBJECT-TYPE
			SYNTAX OCTET STRING
			ACCESS read-only
			STATUS mandatory
			::= { pSysinfo 11 }

		
		-- 1.3.6.1.4.1.22736.3.1.12
		pCpuTop10 OBJECT-TYPE
			SYNTAX OCTET STRING
			ACCESS read-only
			STATUS mandatory
			::= { pSysinfo 12 }

		
		-- 1.3.6.1.4.1.22736.3.1.13
		pMemTop10 OBJECT-TYPE
			SYNTAX OCTET STRING
			ACCESS read-only
			STATUS mandatory
			::= { pSysinfo 13 }

		
--  1.3.6.1.4.1.22736.3.2
		-- 1.3.6.1.4.1.22736.3.2
		pNetstatus OBJECT IDENTIFIER ::= { ippbxPModules 2 }

		
--  1.3.6.1.4.1.22736.3.2.1
		-- 1.3.6.1.4.1.22736.3.2.1
		pDeviceName OBJECT-TYPE
			SYNTAX OCTET STRING
			ACCESS read-only
			STATUS mandatory
			DESCRIPTION
				"Description."
			::= { pNetstatus 1 }

		
--  1.3.6.1.4.1.22736.3.2.2
		-- 1.3.6.1.4.1.22736.3.2.2
		pLanStatus OBJECT-TYPE
			SYNTAX OCTET STRING
			ACCESS read-only
			STATUS mandatory
			DESCRIPTION
				"Description."
			::= { pNetstatus 2 }

		
--  1.3.6.1.4.1.22736.3.2.3
		-- 1.3.6.1.4.1.22736.3.2.3
		pLanMac OBJECT-TYPE
			SYNTAX OCTET STRING
			ACCESS read-only
			STATUS mandatory
			DESCRIPTION
				"Description."
			::= { pNetstatus 3 }


--  1.3.6.1.4.1.22736.3.2.4
		-- 1.3.6.1.4.1.22736.3.2.4
		pLanConnectType OBJECT-TYPE
			SYNTAX OCTET STRING
			ACCESS read-only
			STATUS mandatory
			DESCRIPTION
				"Description."
			::= { pNetstatus 4 }
			

--  1.3.6.1.4.1.22736.3.2.5
		-- 1.3.6.1.4.1.22736.3.2.5
		pLanIpaddress OBJECT-TYPE
			SYNTAX OCTET STRING
			ACCESS read-only
			STATUS mandatory
			DESCRIPTION
				"Description."
			::= { pNetstatus 5 }

		
--  1.3.6.1.4.1.22736.3.2.6
		-- 1.3.6.1.4.1.22736.3.2.6
		pLanSubnetMask OBJECT-TYPE
			SYNTAX OCTET STRING
			ACCESS read-only
			STATUS mandatory
			DESCRIPTION
				"Description."
			::= { pNetstatus 6 }

		
--  1.3.6.1.4.1.22736.3.2.7
		-- 1.3.6.1.4.1.22736.3.2.7
		pLanGateWay OBJECT-TYPE
			SYNTAX OCTET STRING
			ACCESS read-only
			STATUS mandatory
			DESCRIPTION
				"Description."
			::= { pNetstatus 7 }

		
--  1.3.6.1.4.1.22736.3.2.8
		-- 1.3.6.1.4.1.22736.3.2.8
		pLanPrimaryDns OBJECT-TYPE
			SYNTAX OCTET STRING
			ACCESS read-only
			STATUS mandatory
			DESCRIPTION
				"Description."
			::= { pNetstatus 8 }

		
--  1.3.6.1.4.1.22736.3.2.9
		-- 1.3.6.1.4.1.22736.3.2.9
		pLanSecondaryDns OBJECT-TYPE
			SYNTAX OCTET STRING
			ACCESS read-only
			STATUS mandatory
			DESCRIPTION
				"Description."
			::= { pNetstatus 9 }

		
--  1.3.6.1.4.1.22736.3.2.10
		-- 1.3.6.1.4.1.22736.3.2.10
		pWanStatus OBJECT-TYPE
			SYNTAX OCTET STRING
			ACCESS read-only
			STATUS mandatory
			DESCRIPTION
				"Description."
			::= { pNetstatus 10 }

		
--  1.3.6.1.4.1.22736.3.2.11
		-- 1.3.6.1.4.1.22736.3.2.11
		pWanMac OBJECT-TYPE
			SYNTAX OCTET STRING
			ACCESS read-only
			STATUS mandatory
			DESCRIPTION
				"Description."
			::= { pNetstatus 11 }

		
--  1.3.6.1.4.1.22736.3.2.12
		-- 1.3.6.1.4.1.22736.3.2.12
		pWanConnectType OBJECT-TYPE
			SYNTAX OCTET STRING
			ACCESS read-only
			STATUS mandatory
			DESCRIPTION
				"Description."
			::= { pNetstatus 12 }

		
--  1.3.6.1.4.1.22736.3.2.13
		-- 1.3.6.1.4.1.22736.3.2.13
		pWanIpaddress OBJECT-TYPE
			SYNTAX OCTET STRING
			ACCESS read-only
			STATUS mandatory
			DESCRIPTION
				"Description."
			::= { pNetstatus 13 }

		
--  1.3.6.1.4.1.22736.3.2.14
		-- 1.3.6.1.4.1.22736.3.2.14
		pWanSubnetMask OBJECT-TYPE
			SYNTAX OCTET STRING
			ACCESS read-only
			STATUS mandatory
			DESCRIPTION
				"Description."
			::= { pNetstatus 14 }

		
--  1.3.6.1.4.1.22736.3.2.15
		-- 1.3.6.1.4.1.22736.3.2.15
		pWanGateWay OBJECT-TYPE
			SYNTAX OCTET STRING
			ACCESS read-only
			STATUS mandatory
			DESCRIPTION
				"Description."
			::= { pNetstatus 15 }


		
--  1.3.6.1.4.1.22736.3.2.16
		-- 1.3.6.1.4.1.22736.3.2.16
		pWanPrimaryDns OBJECT-TYPE
			SYNTAX OCTET STRING
			ACCESS read-only
			STATUS mandatory
			DESCRIPTION
				"Description."
			::= { pNetstatus 16 }

		
--  1.3.6.1.4.1.22736.3.2.17
		-- 1.3.6.1.4.1.22736.3.2.17
		pWanSecondaryDns OBJECT-TYPE
			SYNTAX OCTET STRING
			ACCESS read-only
			STATUS mandatory
			DESCRIPTION
				"Description."
			::= { pNetstatus 17 }

	
	END

--
-- YEASTAR-P-SERIES-V1.my
--
